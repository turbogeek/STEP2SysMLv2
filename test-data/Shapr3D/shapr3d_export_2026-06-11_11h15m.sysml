package shapr3d_export_2026_06_11_11h15m {
    private import Geometry::*;
    private import ISQ::*;

    part root {
        part root_0 {
            part hull_0 :> Polyhedron {
                :>> vertices = (
                    212.486589 [mm], 212.001533 [mm], 5.000000 [mm], 213.000000 [mm], 206.807692 [mm], 5.000000 [mm], 
                    213.000000 [mm], 206.807692 [mm], 0.000000 [mm], 186.269474 [mm], 206.352046 [mm], 1.002175 [mm], 
                    185.208106 [mm], 206.642941 [mm], 5.000000 [mm], 206.928932 [mm], 213.500000 [mm], 0.000000 [mm], 
                    212.486589 [mm], 212.001533 [mm], 0.000000 [mm], 193.679464 [mm], 213.053003 [mm], 5.000000 [mm], 
                    211.086319 [mm], 213.264027 [mm], 5.000000 [mm], 190.207429 [mm], 211.172638 [mm], 1.355786 [mm], 
                    211.086319 [mm], 213.264027 [mm], 0.000000 [mm], 193.661437 [mm], 212.922566 [mm], 1.956793 [mm], 
                    186.908169 [mm], 209.189878 [mm], 2.519332 [mm], 188.442841 [mm], 210.608536 [mm], 1.967937 [mm], 
                    186.446612 [mm], 207.663310 [mm], 1.355786 [mm], 188.573213 [mm], 210.741543 [mm], 5.000000 [mm], 
                    187.126933 [mm], 209.514668 [mm], 5.000000 [mm]
                );
                :>> faces = (
                    (0, 1, 2), (2, 1, 3), (4, 1, 0), (4, 3, 1), (5, 2, 3), (6, 0, 2), 
                    (6, 2, 5), (7, 4, 0), (8, 0, 6), (8, 7, 0), (8, 5, 7), (9, 5, 3), 
                    (10, 8, 6), (10, 6, 5), (10, 5, 8), (11, 7, 5), (11, 5, 9), (13, 11, 9), 
                    (13, 7, 11), (14, 3, 4), (14, 4, 12), (14, 12, 13), (14, 13, 9), (14, 9, 3), 
                    (15, 4, 7), (15, 7, 13), (16, 12, 4), (16, 4, 15), (16, 15, 13), (16, 13, 12)
                );
            }
            part hull_1 :> Polyhedron {
                :>> vertices = (
                    203.653846 [mm], 119.576923 [mm], 5.000000 [mm], 203.653846 [mm], 109.192308 [mm], 5.000000 [mm], 
                    203.653846 [mm], 109.192308 [mm], 0.000000 [mm], 149.653846 [mm], 116.500000 [mm], 0.000000 [mm], 
                    149.653846 [mm], 112.000000 [mm], 5.000000 [mm], 203.653846 [mm], 119.576923 [mm], 0.000000 [mm], 
                    155.127809 [mm], 118.294975 [mm], 5.000000 [mm], 155.127809 [mm], 110.205025 [mm], 5.000000 [mm], 
                    149.653846 [mm], 116.500000 [mm], 5.000000 [mm], 155.127809 [mm], 118.082843 [mm], 0.975024 [mm], 
                    149.653846 [mm], 112.000000 [mm], 0.000000 [mm], 155.127809 [mm], 110.417157 [mm], 0.975025 [mm]
                );
                :>> faces = (
                    (0, 1, 2), (4, 1, 0), (5, 0, 2), (5, 2, 3), (6, 4, 0), (6, 0, 5), 
                    (7, 2, 1), (7, 1, 4), (8, 6, 3), (8, 3, 4), (8, 4, 6), (9, 6, 5), 
                    (9, 5, 3), (9, 3, 6), (10, 7, 4), (10, 4, 3), (10, 3, 2), (11, 10, 2), 
                    (11, 2, 7), (11, 7, 10)
                );
            }
            part hull_2 :> Polyhedron {
                :>> vertices = (
                    68.653846 [mm], 119.576923 [mm], 5.000000 [mm], 68.653846 [mm], 109.192308 [mm], 5.000000 [mm], 
                    68.653846 [mm], 119.576923 [mm], 0.000000 [mm], -3.000000 [mm], 119.576923 [mm], 0.000000 [mm], 
                    -3.000000 [mm], 109.192308 [mm], 5.000000 [mm], -3.000000 [mm], 109.192308 [mm], 0.000000 [mm], 
                    -3.000000 [mm], 119.576923 [mm], 5.000000 [mm], 68.653846 [mm], 109.192308 [mm], 0.000000 [mm]
                );
                :>> faces = (
                    (0, 1, 2), (4, 1, 0), (5, 3, 2), (5, 4, 3), (5, 1, 4), (6, 4, 0), 
                    (6, 3, 4), (6, 0, 2), (6, 2, 3), (7, 5, 2), (7, 2, 1), (7, 1, 5)
                );
            }
            part hull_3 :> Polyhedron {
                :>> vertices = (
                    164.900079 [mm], 28.220150 [mm], 5.000000 [mm], 165.006681 [mm], 23.851078 [mm], 5.000000 [mm], 
                    164.900079 [mm], 28.220150 [mm], 0.770000 [mm], 115.395366 [mm], 28.698974 [mm], 0.770000 [mm], 
                    113.880528 [mm], 24.851950 [mm], 5.000000 [mm], 144.230769 [mm], 23.230769 [mm], 0.000000 [mm], 
                    165.816199 [mm], 25.543696 [mm], 1.071767 [mm], 115.395366 [mm], 28.698974 [mm], 5.000000 [mm], 
                    135.038462 [mm], 23.961538 [mm], 0.000000 [mm], 115.288764 [mm], 23.372255 [mm], 5.000000 [mm], 
                    165.039295 [mm], 23.951612 [mm], 2.238360 [mm], 113.880528 [mm], 27.148050 [mm], 0.770000 [mm], 
                    114.715186 [mm], 23.796966 [mm], 2.393741 [mm], 113.880528 [mm], 27.148050 [mm], 5.000000 [mm], 
                    113.717473 [mm], 25.623179 [mm], 1.014773 [mm]
                );
                :>> faces = (
                    (0, 2, 3), (4, 1, 0), (6, 0, 1), (6, 2, 0), (6, 5, 2), (7, 4, 0), 
                    (7, 0, 3), (8, 3, 2), (8, 2, 5), (9, 5, 1), (9, 1, 4), (10, 6, 1), 
                    (10, 1, 5), (10, 5, 6), (11, 7, 3), (11, 3, 8), (12, 8, 5), (12, 5, 9), 
                    (12, 9, 4), (13, 4, 7), (13, 7, 11), (14, 11, 8), (14, 8, 12), (14, 12, 4), 
                    (14, 13, 11), (14, 4, 13)
                );
            }
            part hull_4 :> Polyhedron {
                :>> vertices = (
                    153.807692 [mm], 213.500000 [mm], 5.000000 [mm], 153.807692 [mm], 199.500000 [mm], 5.000000 [mm], 
                    153.807692 [mm], 199.500000 [mm], 0.770000 [mm], 126.807692 [mm], 211.500000 [mm], 0.770000 [mm], 
                    126.807692 [mm], 213.038462 [mm], 5.000000 [mm], 130.500000 [mm], 194.346154 [mm], 5.000000 [mm], 
                    153.812387 [mm], 212.268088 [mm], 0.923583 [mm], 149.500000 [mm], 194.346154 [mm], 5.000000 [mm], 
                    130.500000 [mm], 194.346154 [mm], 0.770000 [mm], 126.807692 [mm], 199.500000 [mm], 5.000000 [mm], 
                    140.964342 [mm], 213.083900 [mm], 0.000000 [mm], 147.576923 [mm], 194.346154 [mm], 0.000000 [mm], 
                    126.807692 [mm], 199.500000 [mm], 0.770000 [mm], 126.807692 [mm], 213.441923 [mm], 2.711923 [mm], 
                    153.806484 [mm], 213.347399 [mm], 2.003823 [mm], 149.500000 [mm], 194.346154 [mm], 0.770000 [mm], 
                    137.644656 [mm], 212.841279 [mm], 0.000000 [mm], 126.807692 [mm], 213.500000 [mm], 5.000000 [mm]
                );
                :>> faces = (
                    (4, 1, 0), (5, 1, 4), (6, 0, 1), (6, 1, 2), (7, 2, 1), (7, 1, 5), 
                    (8, 7, 5), (9, 5, 4), (9, 8, 5), (11, 10, 6), (11, 6, 2), (12, 8, 9), 
                    (12, 11, 8), (13, 9, 4), (13, 12, 9), (13, 3, 12), (14, 0, 6), (14, 6, 10), 
                    (14, 13, 0), (14, 10, 13), (15, 11, 2), (15, 2, 7), (15, 7, 8), (15, 8, 11), 
                    (16, 12, 3), (16, 10, 11), (16, 11, 12), (16, 13, 10), (16, 3, 13), (17, 13, 4), 
                    (17, 4, 0), (17, 0, 13)
                );
            }
            part hull_5 :> Polyhedron {
                :>> vertices = (
                    213.000000 [mm], 30.269231 [mm], 5.000000 [mm], 212.489993 [mm], 27.136021 [mm], 5.000000 [mm], 
                    212.489993 [mm], 27.136021 [mm], 0.000000 [mm], 184.805348 [mm], 28.121320 [mm], 0.770000 [mm], 
                    184.805348 [mm], 28.121320 [mm], 5.000000 [mm], 184.805348 [mm], 23.878680 [mm], 5.000000 [mm], 
                    213.000000 [mm], 30.269231 [mm], 0.000000 [mm], 208.863979 [mm], 23.510007 [mm], 5.000000 [mm], 
                    205.346154 [mm], 23.653846 [mm], 0.000000 [mm], 183.999026 [mm], 25.582491 [mm], 1.041203 [mm], 
                    208.863979 [mm], 23.510007 [mm], 0.000000 [mm], 184.585991 [mm], 24.124568 [mm], 2.060000 [mm]
                );
                :>> faces = (
                    (0, 1, 2), (4, 1, 0), (4, 0, 3), (5, 1, 4), (6, 0, 2), (6, 3, 0), 
                    (7, 2, 1), (7, 1, 5), (8, 6, 2), (8, 3, 6), (9, 5, 4), (9, 4, 3), 
                    (9, 3, 8), (10, 7, 5), (10, 8, 2), (10, 2, 7), (11, 9, 8), (11, 5, 9), 
                    (11, 10, 5), (11, 8, 10)
                );
            }
            part hull_6 :> Polyhedron {
                :>> vertices = (
                    94.389911 [mm], 28.377618 [mm], 5.000000 [mm], 94.496512 [mm], 23.693611 [mm], 5.000000 [mm], 
                    94.389911 [mm], 28.377618 [mm], 0.770000 [mm], 64.500000 [mm], 30.269231 [mm], 0.000000 [mm], 
                    64.500000 [mm], 23.000000 [mm], 5.000000 [mm], 95.528341 [mm], 25.488530 [mm], 1.108250 [mm], 
                    64.500000 [mm], 30.269231 [mm], 5.000000 [mm], 65.769231 [mm], 23.230769 [mm], 0.000000 [mm], 
                    94.668941 [mm], 23.833496 [mm], 2.336009 [mm], 74.961538 [mm], 23.961538 [mm], 0.000000 [mm]
                );
                :>> faces = (
                    (0, 2, 3), (4, 1, 0), (5, 0, 1), (5, 2, 0), (6, 4, 0), (6, 0, 3), 
                    (6, 3, 4), (7, 1, 4), (7, 4, 3), (8, 5, 1), (8, 1, 7), (9, 7, 3), 
                    (9, 3, 2), (9, 2, 5), (9, 8, 7), (9, 5, 8)
                );
            }
            part hull_7 :> Polyhedron {
                :>> vertices = (
                    81.115385 [mm], 116.500000 [mm], 5.000000 [mm], 79.500000 [mm], 96.730769 [mm], 5.000000 [mm], 
                    81.115385 [mm], 116.500000 [mm], 0.000000 [mm], 68.653846 [mm], 119.576923 [mm], 0.000000 [mm], 
                    68.653846 [mm], 119.576923 [mm], 5.000000 [mm], 68.653846 [mm], 96.730769 [mm], 0.000000 [mm], 
                    78.000000 [mm], 119.576923 [mm], 5.000000 [mm], 79.500000 [mm], 96.730769 [mm], 0.770000 [mm], 
                    68.653846 [mm], 96.730769 [mm], 5.000000 [mm], 78.000000 [mm], 119.576923 [mm], 0.000000 [mm]
                );
                :>> faces = (
                    (0, 1, 2), (4, 1, 0), (5, 3, 2), (5, 4, 3), (6, 0, 2), (6, 4, 0), 
                    (6, 3, 4), (7, 5, 2), (7, 2, 1), (7, 1, 5), (8, 5, 1), (8, 1, 4), 
                    (8, 4, 5), (9, 6, 2), (9, 2, 3), (9, 3, 6)
                );
            }
            part hull_8 :> Polyhedron {
                :>> vertices = (
                    149.500000 [mm], 194.346154 [mm], 5.000000 [mm], 149.500000 [mm], 30.269231 [mm], 5.000000 [mm], 
                    149.500000 [mm], 194.346154 [mm], 0.770000 [mm], 130.500000 [mm], 194.346154 [mm], 0.770000 [mm], 
                    128.884615 [mm], 29.000000 [mm], 5.000000 [mm], 130.500000 [mm], 194.346154 [mm], 5.000000 [mm], 
                    128.884615 [mm], 29.000000 [mm], 0.770000 [mm], 149.500000 [mm], 30.269231 [mm], 0.770000 [mm]
                );
                :>> faces = (
                    (0, 1, 2), (0, 2, 3), (4, 1, 0), (5, 4, 0), (5, 0, 3), (5, 3, 4), 
                    (6, 1, 4), (6, 4, 3), (6, 3, 2), (7, 6, 2), (7, 2, 1), (7, 1, 6)
                );
            }
            part hull_9 :> Polyhedron {
                :>> vertices = (
                    22.660328 [mm], 209.372520 [mm], 5.000000 [mm], 25.156705 [mm], 200.522579 [mm], 5.000000 [mm], 
                    24.283897 [mm], 199.819320 [mm], 0.879209 [mm], 10.501164 [mm], 212.294842 [mm], 0.935272 [mm], 
                    10.500000 [mm], 199.500000 [mm], 5.000000 [mm], 19.576751 [mm], 211.081104 [mm], 1.355786 [mm], 
                    24.711514 [mm], 206.033941 [mm], 2.004633 [mm], 10.500000 [mm], 213.500000 [mm], 5.000000 [mm], 
                    22.937185 [mm], 199.500000 [mm], 0.770000 [mm], 24.852167 [mm], 206.092201 [mm], 5.000000 [mm], 
                    24.993200 [mm], 200.334357 [mm], 1.262023 [mm], 22.536176 [mm], 209.289565 [mm], 2.004633 [mm], 
                    23.142036 [mm], 207.617464 [mm], 1.355786 [mm], 16.279694 [mm], 212.847677 [mm], 2.004633 [mm], 
                    10.500000 [mm], 199.500000 [mm], 0.770000 [mm], 10.502191 [mm], 213.297753 [mm], 1.908368 [mm], 
                    16.308824 [mm], 212.994124 [mm], 5.000000 [mm]
                );
                :>> faces = (
                    (4, 1, 0), (7, 4, 0), (8, 2, 1), (8, 1, 4), (8, 5, 2), (8, 3, 5), 
                    (9, 0, 1), (10, 1, 2), (10, 9, 1), (10, 6, 9), (11, 5, 0), (11, 9, 6), 
                    (11, 0, 9), (12, 2, 5), (12, 11, 6), (12, 5, 11), (12, 10, 2), (12, 6, 10), 
                    (13, 5, 3), (14, 8, 4), (14, 3, 8), (14, 7, 3), (14, 4, 7), (15, 13, 3), 
                    (15, 3, 7), (15, 7, 13), (16, 13, 7), (16, 7, 0), (16, 0, 5), (16, 5, 13)
                );
            }
            part hull_10 :> Polyhedron {
                :>> vertices = (
                    126.807692 [mm], 213.500000 [mm], 5.000000 [mm], 126.807692 [mm], 199.500000 [mm], 5.000000 [mm], 
                    126.807692 [mm], 211.500000 [mm], 0.770000 [mm], 117.846314 [mm], 207.714163 [mm], 0.895261 [mm], 
                    114.243960 [mm], 200.539152 [mm], 5.000000 [mm], 126.807692 [mm], 199.500000 [mm], 0.770000 [mm], 
                    119.520881 [mm], 211.510605 [mm], 2.726959 [mm], 116.044100 [mm], 199.533500 [mm], 0.775781 [mm], 
                    126.807692 [mm], 213.441923 [mm], 2.711923 [mm], 121.695293 [mm], 211.127659 [mm], 1.223403 [mm], 
                    119.498908 [mm], 211.543490 [mm], 5.000000 [mm], 114.565612 [mm], 206.092201 [mm], 2.770000 [mm], 
                    120.576923 [mm], 199.500000 [mm], 0.770000 [mm], 123.077053 [mm], 212.987778 [mm], 2.770000 [mm], 
                    114.565612 [mm], 206.092201 [mm], 5.000000 [mm], 114.547974 [mm], 200.260437 [mm], 1.948995 [mm], 
                    116.335836 [mm], 206.114545 [mm], 1.211310 [mm], 123.077053 [mm], 212.987778 [mm], 5.000000 [mm]
                );
                :>> faces = (
                    (0, 1, 2), (4, 1, 0), (5, 2, 1), (7, 3, 2), (7, 1, 4), (8, 0, 2), 
                    (9, 2, 3), (9, 3, 6), (10, 4, 0), (11, 6, 3), (11, 10, 6), (12, 7, 2), 
                    (12, 2, 5), (12, 5, 1), (12, 1, 7), (13, 0, 8), (13, 6, 10), (13, 9, 6), 
                    (13, 8, 2), (13, 2, 9), (14, 11, 4), (14, 4, 10), (14, 10, 11), (15, 7, 4), 
                    (15, 4, 11), (16, 11, 3), (16, 3, 7), (16, 15, 11), (16, 7, 15), (17, 13, 10), 
                    (17, 10, 0), (17, 0, 13)
                );
            }
            part hull_11 :> Polyhedron {
                :>> vertices = (
                    83.153589 [mm], 212.844328 [mm], 5.000000 [mm], 82.755205 [mm], 212.923783 [mm], 5.000000 [mm], 
                    52.092006 [mm], 212.769274 [mm], 5.000000 [mm], 52.156775 [mm], 212.375147 [mm], 1.504657 [mm], 
                    72.752775 [mm], 212.759835 [mm], 0.000000 [mm], 83.058158 [mm], 212.365844 [mm], 1.487890 [mm], 
                    72.358723 [mm], 212.837502 [mm], 0.000000 [mm], 66.655291 [mm], 212.644482 [mm], 0.000000 [mm], 
                    82.726003 [mm], 212.777367 [mm], 2.004633 [mm], 52.489408 [mm], 212.848322 [mm], 5.000000 [mm], 
                    52.467519 [mm], 212.728694 [mm], 1.934979 [mm], 67.052693 [mm], 212.723530 [mm], 0.000000 [mm]
                );
                :>> faces = (
                    (0, 1, 2), (5, 0, 2), (5, 2, 3), (6, 5, 4), (7, 5, 3), (7, 4, 5), 
                    (7, 6, 4), (8, 1, 0), (8, 0, 5), (8, 6, 1), (8, 5, 6), (9, 2, 1), 
                    (9, 1, 6), (10, 9, 6), (10, 3, 2), (10, 2, 9), (11, 7, 3), (11, 3, 10), 
                    (11, 10, 6), (11, 6, 7)
                );
            }
            part hull_12 :> Polyhedron {
                :>> vertices = (
                    91.851128 [mm], 207.737852 [mm], 5.000000 [mm], 93.917957 [mm], 200.376076 [mm], 5.000000 [mm], 
                    93.923546 [mm], 203.581013 [mm], 1.355786 [mm], 80.919301 [mm], 212.055311 [mm], 0.922241 [mm], 
                    81.115385 [mm], 199.500000 [mm], 5.000000 [mm], 87.918702 [mm], 210.794470 [mm], 2.004633 [mm], 
                    93.444650 [mm], 205.339717 [mm], 5.000000 [mm], 81.115385 [mm], 213.038462 [mm], 5.000000 [mm], 
                    79.500000 [mm], 198.500000 [mm], 0.770000 [mm], 93.320300 [mm], 205.257088 [mm], 2.004633 [mm], 
                    86.249031 [mm], 211.401945 [mm], 1.355786 [mm], 88.001839 [mm], 210.918482 [mm], 5.000000 [mm], 
                    93.006350 [mm], 200.409230 [mm], 1.355786 [mm], 93.890014 [mm], 201.292893 [mm], 1.355786 [mm], 
                    91.500000 [mm], 200.095464 [mm], 1.349320 [mm], 93.671601 [mm], 200.482246 [mm], 2.004633 [mm]
                );
                :>> faces = (
                    (4, 1, 0), (6, 0, 1), (6, 1, 2), (7, 4, 0), (8, 1, 4), (8, 3, 2), 
                    (8, 7, 3), (8, 4, 7), (9, 5, 0), (9, 2, 5), (9, 6, 2), (9, 0, 6), 
                    (10, 5, 2), (10, 2, 3), (10, 3, 7), (11, 7, 0), (11, 0, 5), (11, 10, 7), 
                    (11, 5, 10), (13, 12, 8), (13, 8, 2), (13, 2, 1), (14, 1, 8), (14, 8, 12), 
                    (15, 13, 1), (15, 12, 13), (15, 14, 12), (15, 1, 14)
                );
            }
            part hull_13 :> Polyhedron {
                :>> vertices = (
                    60.500000 [mm], 30.269231 [mm], 5.000000 [mm], 60.346154 [mm], 23.000000 [mm], 5.000000 [mm], 
                    60.500000 [mm], 30.269231 [mm], 0.770000 [mm], 45.004941 [mm], 28.362298 [mm], 0.770000 [mm], 
                    44.898339 [mm], 23.708931 [mm], 5.000000 [mm], 60.394756 [mm], 26.966202 [mm], 0.827230 [mm], 
                    45.004941 [mm], 28.362298 [mm], 5.000000 [mm], 60.346154 [mm], 23.796828 [mm], 3.038988 [mm], 
                    43.858805 [mm], 25.462271 [mm], 1.119294 [mm], 44.517431 [mm], 24.049507 [mm], 2.136468 [mm]
                );
                :>> faces = (
                    (0, 1, 2), (0, 2, 3), (4, 1, 0), (5, 3, 2), (6, 4, 0), (6, 0, 3), 
                    (7, 5, 2), (7, 2, 1), (8, 6, 3), (8, 4, 6), (8, 3, 5), (8, 5, 7), 
                    (9, 7, 1), (9, 1, 4), (9, 8, 7), (9, 4, 8)
                );
            }
            part hull_14 :> Polyhedron {
                :>> vertices = (
                    160.796537 [mm], 211.064666 [mm], 5.000000 [mm], 164.830292 [mm], 200.050510 [mm], 5.000000 [mm], 
                    164.472027 [mm], 205.868030 [mm], 1.355786 [mm], 153.812387 [mm], 212.268088 [mm], 0.923583 [mm], 
                    153.807692 [mm], 199.500000 [mm], 5.000000 [mm], 159.041481 [mm], 211.546374 [mm], 1.355786 [mm], 
                    164.110973 [mm], 207.442514 [mm], 5.000000 [mm], 153.807692 [mm], 213.500000 [mm], 5.000000 [mm], 
                    153.807692 [mm], 199.500000 [mm], 0.770000 [mm], 160.713581 [mm], 210.940515 [mm], 2.004633 [mm], 
                    153.806484 [mm], 213.347399 [mm], 2.003823 [mm], 157.498880 [mm], 212.789443 [mm], 5.000000 [mm], 
                    164.474093 [mm], 199.838573 [mm], 0.892949 [mm], 163.986821 [mm], 207.359558 [mm], 2.004633 [mm], 
                    157.469750 [mm], 212.642996 [mm], 2.004633 [mm]
                );
                :>> faces = (
                    (4, 1, 0), (5, 2, 3), (6, 0, 1), (6, 1, 2), (7, 4, 0), (9, 2, 5), 
                    (9, 0, 6), (10, 3, 8), (10, 8, 4), (10, 4, 7), (11, 7, 0), (12, 2, 1), 
                    (12, 1, 4), (12, 4, 8), (12, 8, 3), (12, 3, 2), (13, 9, 6), (13, 6, 2), 
                    (13, 2, 9), (14, 5, 3), (14, 3, 10), (14, 10, 7), (14, 7, 11), (14, 9, 5), 
                    (14, 11, 0), (14, 0, 9)
                );
            }
            part hull_15 :> Polyhedron {
                :>> vertices = (
                    81.115385 [mm], 213.038462 [mm], 5.000000 [mm], 81.115385 [mm], 206.807692 [mm], 5.000000 [mm], 
                    81.115385 [mm], 206.807692 [mm], 0.770000 [mm], 46.328641 [mm], 206.626209 [mm], 0.922241 [mm], 
                    44.716875 [mm], 206.148798 [mm], 5.000000 [mm], 80.919301 [mm], 212.055311 [mm], 0.922241 [mm], 
                    49.108483 [mm], 211.206814 [mm], 5.000000 [mm], 45.240950 [mm], 206.281590 [mm], 1.879010 [mm], 
                    50.796588 [mm], 211.611729 [mm], 1.355786 [mm], 47.428682 [mm], 209.628457 [mm], 2.087000 [mm], 
                    45.537696 [mm], 207.385785 [mm], 1.950779 [mm], 45.676288 [mm], 207.584661 [mm], 5.000000 [mm], 
                    48.933759 [mm], 211.054519 [mm], 2.148778 [mm], 46.945837 [mm], 207.948619 [mm], 1.132653 [mm]
                );
                :>> faces = (
                    (0, 1, 2), (4, 1, 0), (4, 2, 1), (5, 0, 2), (5, 2, 3), (6, 4, 0), 
                    (7, 3, 2), (7, 2, 4), (8, 5, 3), (8, 6, 0), (8, 0, 5), (10, 7, 4), 
                    (10, 3, 7), (11, 4, 6), (11, 6, 9), (11, 10, 4), (11, 9, 10), (12, 9, 6), 
                    (12, 6, 8), (13, 8, 3), (13, 10, 9), (13, 3, 10), (13, 12, 8), (13, 9, 12)
                );
            }
            part hull_16 :> Polyhedron {
                :>> vertices = (
                    79.500000 [mm], 36.500000 [mm], 5.000000 [mm], 81.115385 [mm], 29.000000 [mm], 5.000000 [mm], 
                    81.115385 [mm], 29.000000 [mm], 0.770000 [mm], 64.500000 [mm], 36.500000 [mm], 0.000000 [mm], 
                    64.500000 [mm], 30.269231 [mm], 5.000000 [mm], 79.500000 [mm], 36.500000 [mm], 0.770000 [mm], 
                    64.500000 [mm], 36.500000 [mm], 5.000000 [mm], 64.500000 [mm], 30.269231 [mm], 0.000000 [mm]
                );
                :>> faces = (
                    (0, 1, 2), (4, 1, 0), (4, 2, 1), (5, 0, 2), (5, 2, 3), (5, 3, 0), 
                    (6, 4, 0), (6, 0, 3), (7, 3, 2), (7, 2, 4), (7, 6, 3), (7, 4, 6)
                );
            }
            part hull_17 :> Polyhedron {
                :>> vertices = (
                    10.500000 [mm], 213.500000 [mm], 5.000000 [mm], 9.294975 [mm], 123.413212 [mm], 5.000000 [mm], 
                    8.000000 [mm], 119.576923 [mm], 0.000000 [mm], -1.974874 [mm], 213.596194 [mm], 0.000000 [mm], 
                    -3.000000 [mm], 206.807692 [mm], 5.000000 [mm], 10.501164 [mm], 212.294842 [mm], 0.935272 [mm], 
                    -1.974874 [mm], 213.596194 [mm], 5.000000 [mm], -3.000000 [mm], 119.576923 [mm], 5.000000 [mm], 
                    2.974874 [mm], 213.596194 [mm], 0.000000 [mm], 10.500000 [mm], 206.807692 [mm], 0.770000 [mm], 
                    8.000000 [mm], 119.576923 [mm], 5.000000 [mm], -3.000000 [mm], 119.576923 [mm], 0.000000 [mm], 
                    10.502191 [mm], 213.297753 [mm], 1.908368 [mm], 8.000000 [mm], 121.653846 [mm], 0.000000 [mm]
                );
                :>> faces = (
                    (4, 1, 0), (6, 4, 0), (6, 3, 4), (7, 1, 4), (8, 2, 3), (8, 6, 0), 
                    (8, 3, 6), (9, 0, 1), (9, 1, 2), (9, 8, 5), (10, 7, 2), (10, 2, 1), 
                    (10, 1, 7), (11, 7, 4), (11, 4, 3), (11, 3, 2), (11, 2, 7), (12, 8, 0), 
                    (12, 5, 8), (12, 9, 5), (12, 0, 9), (13, 9, 2), (13, 2, 8), (13, 8, 9)
                );
            }
            part hull_18 :> Polyhedron {
                :>> vertices = (
                    79.500000 [mm], 194.346154 [mm], 5.000000 [mm], 79.294975 [mm], 123.413212 [mm], 5.000000 [mm], 
                    78.000000 [mm], 119.576923 [mm], 0.000000 [mm], 60.500000 [mm], 194.346154 [mm], 0.770000 [mm], 
                    60.500000 [mm], 194.346154 [mm], 5.000000 [mm], 79.500000 [mm], 194.346154 [mm], 0.770000 [mm], 
                    62.000000 [mm], 119.576923 [mm], 5.000000 [mm], 79.294975 [mm], 123.413212 [mm], 0.770000 [mm], 
                    78.000000 [mm], 119.576923 [mm], 5.000000 [mm], 62.000000 [mm], 119.576923 [mm], 0.000000 [mm]
                );
                :>> faces = (
                    (4, 1, 0), (4, 0, 3), (5, 2, 3), (5, 3, 0), (5, 0, 1), (6, 1, 4), 
                    (7, 5, 1), (7, 1, 2), (7, 2, 5), (8, 2, 1), (8, 1, 6), (9, 3, 2), 
                    (9, 8, 6), (9, 2, 8), (9, 6, 4), (9, 4, 3)
                );
            }
            part hull_19 :> Polyhedron {
                :>> vertices = (
                    79.500000 [mm], 96.730769 [mm], 5.000000 [mm], 79.500000 [mm], 36.500000 [mm], 5.000000 [mm], 
                    79.500000 [mm], 36.500000 [mm], 0.770000 [mm], 60.500000 [mm], 96.730769 [mm], 0.770000 [mm], 
                    60.500000 [mm], 96.730769 [mm], 5.000000 [mm], 60.500000 [mm], 36.500000 [mm], 0.770000 [mm], 
                    79.500000 [mm], 96.730769 [mm], 0.770000 [mm], 74.884615 [mm], 36.500000 [mm], 0.000000 [mm], 
                    60.500000 [mm], 36.500000 [mm], 5.000000 [mm]
                );
                :>> faces = (
                    (0, 1, 2), (4, 1, 0), (5, 2, 1), (5, 4, 3), (6, 0, 2), (6, 4, 0), 
                    (6, 3, 4), (7, 5, 3), (7, 2, 5), (7, 6, 2), (7, 3, 6), (8, 5, 1), 
                    (8, 1, 4), (8, 4, 5)
                );
            }
            part hull_20 :> Polyhedron {
                :>> vertices = (
                    8.000000 [mm], 109.192308 [mm], 5.000000 [mm], 9.500000 [mm], 30.269231 [mm], 5.000000 [mm], 
                    8.000000 [mm], 109.192308 [mm], 0.000000 [mm], -3.000000 [mm], 109.192308 [mm], 0.000000 [mm], 
                    -3.000000 [mm], 30.269231 [mm], 5.000000 [mm], 9.152339 [mm], 105.098468 [mm], 5.000000 [mm], 
                    -3.000000 [mm], 109.192308 [mm], 5.000000 [mm], -3.000000 [mm], 30.269231 [mm], 0.000000 [mm], 
                    9.500000 [mm], 30.269231 [mm], 0.770000 [mm], 6.346154 [mm], 30.269231 [mm], 0.000000 [mm], 
                    8.000000 [mm], 107.115385 [mm], 0.000000 [mm]
                );
                :>> faces = (
                    (0, 2, 3), (4, 1, 0), (5, 0, 1), (5, 2, 0), (6, 4, 0), (6, 0, 3), 
                    (6, 3, 4), (7, 1, 4), (7, 4, 3), (7, 3, 2), (8, 5, 1), (8, 2, 5), 
                    (8, 1, 7), (9, 8, 7), (9, 7, 2), (10, 9, 2), (10, 2, 8), (10, 8, 9)
                );
            }
            part hull_21 :> Polyhedron {
                :>> vertices = (
                    128.884615 [mm], 116.500000 [mm], 5.000000 [mm], 128.884615 [mm], 112.000000 [mm], 5.000000 [mm], 
                    128.884615 [mm], 116.500000 [mm], 0.000000 [mm], 81.115385 [mm], 116.500000 [mm], 0.000000 [mm], 
                    81.115385 [mm], 112.000000 [mm], 5.000000 [mm], 124.170917 [mm], 110.300000 [mm], 0.770000 [mm], 
                    124.665887 [mm], 118.294980 [mm], 1.187154 [mm], 84.318362 [mm], 118.294975 [mm], 5.000000 [mm], 
                    128.884615 [mm], 112.000000 [mm], 0.000000 [mm], 84.318363 [mm], 110.417157 [mm], 0.975025 [mm], 
                    84.318362 [mm], 110.205025 [mm], 5.000000 [mm], 124.170917 [mm], 118.200000 [mm], 0.770000 [mm], 
                    81.115385 [mm], 116.500000 [mm], 5.000000 [mm], 124.734793 [mm], 118.191856 [mm], 5.000000 [mm], 
                    124.690362 [mm], 110.243952 [mm], 1.123760 [mm], 81.115385 [mm], 112.000000 [mm], 0.000000 [mm], 
                    84.368540 [mm], 118.094719 [mm], 0.954241 [mm], 124.817633 [mm], 110.432122 [mm], 5.000000 [mm]
                );
                :>> faces = (
                    (0, 1, 2), (4, 1, 0), (6, 0, 2), (7, 4, 0), (8, 2, 1), (8, 3, 2), 
                    (10, 1, 4), (11, 6, 2), (11, 2, 3), (12, 7, 3), (12, 3, 4), (12, 4, 7), 
                    (13, 7, 0), (13, 0, 6), (13, 6, 7), (14, 8, 1), (14, 5, 8), (14, 10, 9), 
                    (14, 9, 5), (15, 4, 3), (15, 3, 8), (15, 8, 5), (15, 5, 9), (15, 10, 4), 
                    (15, 9, 10), (16, 7, 6), (16, 6, 11), (16, 11, 3), (16, 3, 7), (17, 14, 1), 
                    (17, 1, 10), (17, 10, 14)
                );
            }
            part hull_22 :> Polyhedron {
                :>> vertices = (
                    213.000000 [mm], 206.807692 [mm], 5.000000 [mm], 213.000000 [mm], 119.576923 [mm], 5.000000 [mm], 
                    213.000000 [mm], 206.807692 [mm], 0.000000 [mm], 199.500000 [mm], 206.807692 [mm], 0.770000 [mm], 
                    199.500000 [mm], 206.807692 [mm], 5.000000 [mm], 202.000000 [mm], 119.576923 [mm], 0.000000 [mm], 
                    213.000000 [mm], 119.576923 [mm], 0.000000 [mm], 202.000000 [mm], 121.653846 [mm], 0.000000 [mm], 
                    200.705025 [mm], 123.413212 [mm], 5.000000 [mm], 202.000000 [mm], 119.576923 [mm], 5.000000 [mm]
                );
                :>> faces = (
                    (0, 1, 2), (4, 1, 0), (4, 0, 2), (4, 2, 3), (6, 5, 2), (6, 2, 1), 
                    (6, 1, 5), (7, 5, 3), (7, 3, 2), (7, 2, 5), (8, 4, 3), (8, 3, 5), 
                    (8, 1, 4), (9, 8, 5), (9, 5, 1), (9, 1, 8)
                );
            }
            part hull_23 :> Polyhedron {
                :>> vertices = (
                    213.000000 [mm], 96.730769 [mm], 5.000000 [mm], 213.000000 [mm], 30.269231 [mm], 5.000000 [mm], 
                    213.000000 [mm], 96.730769 [mm], 0.000000 [mm], 200.500000 [mm], 96.730769 [mm], 0.770000 [mm], 
                    200.500000 [mm], 30.269231 [mm], 5.000000 [mm], 200.500000 [mm], 96.730769 [mm], 5.000000 [mm], 
                    213.000000 [mm], 30.269231 [mm], 0.000000 [mm], 200.500000 [mm], 30.269231 [mm], 0.770000 [mm]
                );
                :>> faces = (
                    (0, 1, 2), (0, 2, 3), (4, 1, 0), (5, 4, 0), (5, 0, 3), (5, 3, 4), 
                    (6, 2, 1), (6, 1, 4), (6, 3, 2), (7, 6, 4), (7, 4, 3), (7, 3, 6)
                );
            }
            part hull_24 :> Polyhedron {
                :>> vertices = (
                    81.115385 [mm], 206.807692 [mm], 5.000000 [mm], 79.500000 [mm], 194.346154 [mm], 5.000000 [mm], 
                    81.115385 [mm], 204.730769 [mm], 0.770000 [mm], 56.192308 [mm], 206.807692 [mm], 0.770000 [mm], 
                    56.192308 [mm], 206.807692 [mm], 5.000000 [mm], 60.500000 [mm], 194.346154 [mm], 0.770000 [mm], 
                    81.115385 [mm], 206.807692 [mm], 0.770000 [mm], 79.500000 [mm], 194.346154 [mm], 0.770000 [mm], 
                    56.192308 [mm], 199.500000 [mm], 5.000000 [mm], 56.192308 [mm], 199.500000 [mm], 0.770000 [mm], 
                    60.500000 [mm], 194.346154 [mm], 5.000000 [mm]
                );
                :>> faces = (
                    (0, 1, 2), (4, 1, 0), (4, 0, 3), (5, 3, 2), (6, 0, 2), (6, 2, 3), 
                    (6, 3, 0), (7, 5, 2), (7, 2, 1), (7, 1, 5), (8, 4, 3), (8, 1, 4), 
                    (9, 8, 3), (9, 3, 5), (9, 5, 8), (10, 8, 5), (10, 5, 1), (10, 1, 8)
                );
            }
            part hull_25 :> Polyhedron {
                :>> vertices = (
                    56.192308 [mm], 206.807692 [mm], 5.000000 [mm], 56.192308 [mm], 199.500000 [mm], 5.000000 [mm], 
                    56.192308 [mm], 199.500000 [mm], 0.770000 [mm], 45.500651 [mm], 206.191117 [mm], 1.355786 [mm], 
                    44.716875 [mm], 206.148798 [mm], 5.000000 [mm], 56.192308 [mm], 206.807692 [mm], 0.770000 [mm], 
                    45.083173 [mm], 199.914422 [mm], 0.943408 [mm], 44.861989 [mm], 200.050510 [mm], 5.000000 [mm]
                );
                :>> faces = (
                    (0, 1, 2), (4, 1, 0), (5, 0, 2), (5, 4, 0), (5, 3, 4), (6, 2, 1), 
                    (6, 4, 3), (6, 5, 2), (6, 3, 5), (7, 6, 1), (7, 1, 4), (7, 4, 6)
                );
            }
            part hull_26 :> Polyhedron {
                :>> vertices = (
                    199.500000 [mm], 206.807692 [mm], 5.000000 [mm], 200.500000 [mm], 198.500000 [mm], 5.000000 [mm], 
                    199.500000 [mm], 206.807692 [mm], 0.770000 [mm], 186.269474 [mm], 206.352046 [mm], 1.002175 [mm], 
                    184.694373 [mm], 200.368798 [mm], 5.000000 [mm], 200.500000 [mm], 198.500000 [mm], 0.770000 [mm], 
                    184.840114 [mm], 206.092201 [mm], 5.000000 [mm], 185.621456 [mm], 199.722438 [mm], 0.823007 [mm], 
                    184.648522 [mm], 200.391802 [mm], 1.309839 [mm], 185.098571 [mm], 206.036415 [mm], 2.270723 [mm]
                );
                :>> faces = (
                    (0, 1, 2), (0, 2, 3), (4, 1, 0), (5, 2, 1), (6, 4, 0), (6, 0, 3), 
                    (7, 3, 2), (7, 2, 5), (7, 5, 1), (7, 1, 4), (8, 3, 7), (8, 7, 4), 
                    (8, 4, 6), (9, 8, 6), (9, 6, 3), (9, 3, 8)
                );
            }
            part hull_27 :> Polyhedron {
                :>> vertices = (
                    203.653846 [mm], 109.192308 [mm], 5.000000 [mm], 203.653846 [mm], 96.730769 [mm], 5.000000 [mm], 
                    203.653846 [mm], 96.730769 [mm], 0.000000 [mm], 202.000000 [mm], 109.192308 [mm], 0.000000 [mm], 
                    200.500000 [mm], 96.730769 [mm], 5.000000 [mm], 203.653846 [mm], 109.192308 [mm], 0.000000 [mm], 
                    200.553284 [mm], 104.776065 [mm], 5.000000 [mm], 200.500000 [mm], 96.730769 [mm], 0.770000 [mm], 
                    202.000000 [mm], 109.192308 [mm], 5.000000 [mm], 202.000000 [mm], 107.115385 [mm], 0.000000 [mm]
                );
                :>> faces = (
                    (0, 1, 2), (4, 1, 0), (4, 2, 1), (5, 0, 2), (5, 2, 3), (5, 3, 0), 
                    (6, 4, 0), (7, 2, 4), (7, 6, 3), (7, 4, 6), (8, 6, 0), (8, 0, 3), 
                    (8, 3, 6), (9, 7, 3), (9, 3, 2), (9, 2, 7)
                );
            }
            part hull_28 :> Polyhedron {
                :>> vertices = (
                    64.500000 [mm], 36.500000 [mm], 5.000000 [mm], 65.769231 [mm], 23.230769 [mm], 1.038462 [mm], 
                    64.500000 [mm], 36.500000 [mm], 0.000000 [mm], 60.500000 [mm], 36.500000 [mm], 0.770000 [mm], 
                    60.346154 [mm], 23.000000 [mm], 5.000000 [mm], 63.692308 [mm], 25.307692 [mm], 0.000000 [mm], 
                    64.500000 [mm], 23.000000 [mm], 5.000000 [mm], 60.500000 [mm], 36.500000 [mm], 5.000000 [mm], 
                    64.730769 [mm], 24.269231 [mm], 0.000000 [mm], 60.394756 [mm], 26.966202 [mm], 0.827230 [mm], 
                    60.346154 [mm], 23.796828 [mm], 3.038988 [mm]
                );
                :>> faces = (
                    (0, 1, 2), (5, 3, 2), (6, 4, 1), (6, 1, 0), (6, 0, 4), (7, 4, 0), 
                    (7, 0, 2), (7, 2, 3), (8, 5, 2), (8, 2, 1), (9, 3, 5), (9, 5, 8), 
                    (10, 7, 3), (10, 4, 7), (10, 3, 9), (10, 9, 8), (10, 8, 1), (10, 1, 4)
                );
            }
            part hull_29 :> Polyhedron {
                :>> vertices = (
                    23.999486 [mm], 28.714293 [mm], 5.000000 [mm], 25.537251 [mm], 24.851950 [mm], 5.000000 [mm], 
                    25.537251 [mm], 27.148050 [mm], 0.770000 [mm], -3.000000 [mm], 30.269231 [mm], 0.000000 [mm], 
                    -2.111295 [mm], 25.326153 [mm], 5.000000 [mm], 23.999486 [mm], 28.714293 [mm], 0.770000 [mm], 
                    25.537251 [mm], 27.148050 [mm], 5.000000 [mm], -3.000000 [mm], 30.269231 [mm], 5.000000 [mm], 
                    4.653846 [mm], 23.653846 [mm], 0.000000 [mm], 25.694604 [mm], 25.706696 [mm], 0.963971 [mm], 
                    24.106087 [mm], 23.356935 [mm], 5.000000 [mm], -0.673847 [mm], 23.888705 [mm], 0.000000 [mm], 
                    24.641044 [mm], 23.659323 [mm], 2.480000 [mm], -2.111295 [mm], 25.326153 [mm], 0.000000 [mm], 
                    -0.673847 [mm], 23.888705 [mm], 5.000000 [mm]
                );
                :>> faces = (
                    (4, 1, 0), (6, 0, 1), (6, 5, 0), (6, 2, 5), (7, 4, 0), (7, 3, 4), 
                    (7, 5, 3), (7, 0, 5), (8, 5, 2), (8, 3, 5), (9, 6, 1), (9, 2, 6), 
                    (9, 8, 2), (10, 1, 4), (11, 3, 8), (12, 9, 1), (12, 1, 10), (12, 10, 8), 
                    (12, 8, 9), (13, 11, 4), (13, 4, 3), (13, 3, 11), (14, 10, 4), (14, 4, 11), 
                    (14, 11, 8), (14, 8, 10)
                );
            }
            part hull_30 :> Polyhedron {
                :>> vertices = (
                    68.653846 [mm], 109.192308 [mm], 5.000000 [mm], 68.653846 [mm], 96.730769 [mm], 5.000000 [mm], 
                    68.653846 [mm], 109.192308 [mm], 0.000000 [mm], 62.000000 [mm], 109.192308 [mm], 0.000000 [mm], 
                    60.500000 [mm], 96.730769 [mm], 5.000000 [mm], 62.000000 [mm], 109.192308 [mm], 5.000000 [mm], 
                    68.653846 [mm], 96.730769 [mm], 0.000000 [mm], 60.500000 [mm], 96.730769 [mm], 0.770000 [mm]
                );
                :>> faces = (
                    (0, 1, 2), (0, 2, 3), (4, 1, 0), (5, 4, 0), (5, 0, 3), (5, 3, 4), 
                    (6, 2, 1), (6, 3, 2), (7, 4, 3), (7, 3, 6), (7, 6, 1), (7, 1, 4)
                );
            }
            part hull_31 :> Polyhedron {
                :>> vertices = (
                    213.000000 [mm], 119.576923 [mm], 5.000000 [mm], 213.000000 [mm], 96.730769 [mm], 5.000000 [mm], 
                    213.000000 [mm], 119.576923 [mm], 0.000000 [mm], 203.653846 [mm], 119.576923 [mm], 0.000000 [mm], 
                    203.653846 [mm], 119.576923 [mm], 5.000000 [mm], 203.653846 [mm], 96.730769 [mm], 0.000000 [mm], 
                    213.000000 [mm], 96.730769 [mm], 0.000000 [mm], 203.653846 [mm], 96.730769 [mm], 5.000000 [mm]
                );
                :>> faces = (
                    (0, 1, 2), (0, 2, 3), (4, 1, 0), (4, 0, 3), (5, 3, 2), (6, 5, 2), 
                    (6, 2, 1), (6, 1, 5), (7, 5, 1), (7, 1, 4), (7, 4, 3), (7, 3, 5)
                );
            }
        }
    }
}
